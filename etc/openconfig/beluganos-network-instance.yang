module beluganos-network-instance {

  yang-version "1";

  // namespace
  namespace "https://github.com/beluganos/beluganos/yang/network-instance";

  prefix "boc-netinst";

  // import some basic types
  // import ietf-inet-types { prefix inet; }
  import ietf-yang-types { prefix "yang"; }
  import openconfig-network-instance-types { prefix "oc-ni-types"; }
  import openconfig-policy-types { prefix "oc-pol-types"; }
  import openconfig-extensions { prefix "oc-ext"; }

  import beluganos-local-routing { prefix "boc-loc-rt"; }
  import beluganos-mpls { prefix "boc-mpls"; }
  import beluganos-bgp { prefix "boc-bgp"; }
  import beluganos-ospfv2 { prefix "boc-ospfv2"; }
  import beluganos-ospfv3 { prefix "boc-ospfv3"; }
  import beluganos-interfaces { prefix "boc-if"; }

  // meta
  organization "Nippon Telegraph and Telephone Corporation";

  contact
    "NTT R&D
    https://github.com/beluganos";

  description
    "An OpenConfig description of a network-instance. This may be
    a Layer 3 forwarding construct such as a virtual routing and
    forwarding (VRF) instance, or a Layer 2 instance such as a
    virtual switch instance (VSI). Mixed Layer 2 and Layer 3
    instances are also supported.";

  oc-ext:openconfig-version "0.8.1";

  revision "2017-10-20" {
    description
      "Minor formatting fixes";
    reference "0.0.1";
  }

  grouping network-instance-loopback-config {
    leaf id {
      type string;
    }
  }

  grouping network-instance-loopback-address-config {
    leaf index {
      type uint32;
    }

    leaf ip {
      //@BEL changed to string
      // type inet:ipv4-address;
      type string;
    }

    leaf prefix-length {
      type uint8 {
        range "0..128";
      }
    }
  }

  grouping network-instance-loopbacks {
    list loopback {
      key "id";
      unique "config/id";

      leaf id {
        type leafref {
          path "../config/id";
        }
      }

      container config {
        uses network-instance-loopback-config;
      }

      container addresses {
        list address {
          key "index";
          leaf index {
            type leafref {
              path "../config/index";
            }
          }

          container config {
            uses network-instance-loopback-address-config;
          }
        }
      }
    }
  }

  grouping network-instance-top {
    description
      "Top-level grouping containing a list of network instances.";

    container network-instances {
      description
        "The L2, L3, or L2+L3 forwarding instances that are
        configured on the local system";

      list network-instance {
        key "name";

        description
          "Network instances configured on the local system";

        leaf name {
          type leafref {
            path "../config/name";
          }
          description
            "A unique name identifying the network instance";
        }

        container config {
          description
            "Configuration parameters relating to a network
            instance";
          uses network-instance-config;
        }

        container loopbacks {
          uses network-instance-loopbacks;
        }

        container state {
          // @BEL
          // config false;
          description
            "Operational state parameters relating to a network
            instance";
          //uses network-instance-config;
          //uses network-instance-type-dependent-config;
          //uses network-instance-state;
        }

        container interfaces {
          description
            "The interfaces that are associated with this network
            instance";

          list interface {
            key "id";
            unique "config/interface config/subinterface";

            description
              "An interface associated with the network instance";

            leaf id {
              type leafref {
                path "../config/id";
              }
              description
                "A reference to an identifier for this interface which
                acts as a key for this list";
            }

            container config {
              description
                "Configuration parameters relating to the associated
                interface";
              uses instance-interfaces-config;
            }

            container state {
              // @BEL
              //config false;
              description
                "Operational state parameters relating to the
                associated interface";

              //uses instance-interfaces-config;
              //uses instance-interfaces-state;
            }
          }
        }

        uses boc-mpls:mpls-top {
          //when "../config/type = 'DEFAULT'" {
          //description
          //  "MPLS configuration is only valid within the default
          //    network instance.";
          //}
        }

        container protocols {
          description
            "The routing protocols that are enabled for this
            network-instance.";

          list protocol {
            key "identifier name";

            description
              "A process (instance) of a routing protocol. Some
              systems may not support more than one instance of
              a particular routing protocol";

            leaf identifier {
              type leafref {
                path "../config/identifier";
              }
              description
                "The protocol name for the routing or forwarding
                protocol to be instantiated";
            }

            leaf name {
              type leafref {
                path "../config/name";
              }
              description
                "An operator-assigned identifier for the routing
                or forwarding protocol. For some processes this
                leaf may be system defined.";
            }

            container config {
              description
                "Configuration parameters relating to the routing
                protocol instance";

              uses protocols-config;
            }

            container state {
              // @BEL
              //config false;
              description
                "State parameters relating to the routing protocol
                instance";

              //uses protocols-config;
              //uses protocols-state;
            }

            uses boc-loc-rt:local-static-top {
              //when "../config/identifier = 'STATIC'" {
              //  description
              //    "Include static route parameters only when the
              //    protocol is set to static";
              //}
              description
                "Configuration and state parameters relating to
                static routes";
            }

            uses boc-bgp:bgp-top {
              //when "../config/identifier = 'BGP'" {
              //  description
              //    "Include BGP parameters only when the protocol
              //    is of type BGP";
              //}
              description
                "Configuration and state parameters relating to
                Border Gateway Protocol (BGP)";
            }

            uses boc-ospfv2:ospfv2-top {
              //when "../config/identifier = 'OSPF2'" {
              //  description
              //    "Include OSPFv2 parameters only when the protocol
              //    is of type OSPFv2";
              //}
            }

            uses boc-ospfv3:ospfv3-top {
              //when "../config/identifier = 'OSPF2'" {
              //  description
              //    "Include OSPFv2 parameters only when the protocol
              //    is of type OSPFv2";
              //}
            }
          }
        }
      }
    }
  }

  grouping instance-interfaces-config {
    description
      "Configuration parameters related to an interface associated
      with the network instance";

    leaf id {
      type string;
      description
        "A unique identifier for this interface - this is expressed
        as a free-text string";
    }

    uses boc-if:interface-ref-common;
  }

  grouping network-instance-config {
    description
      "Configuration parameters relating to a top-level network
      instance";

    leaf name {
      type string;
      description
        "An operator-assigned unique name for the forwarding
        instance";
    }

    leaf type {
      type identityref {
        base "oc-ni-types:NETWORK_INSTANCE_TYPE";
      }
      description
        "The type of network instance. The value of this leaf
        indicates the type of forwarding entries that should be
        supported by this network instance";
    }

    leaf description {
      type string;
      description
        "A free-form string to be used by the network operator to
        describe the function of this network instance";
    }

    leaf router-id {
      type yang:dotted-quad;
      description
        "A identifier for the local network instance - typically
        used within associated routing protocols or signalling
        routing information in another network instance";
    }

    leaf route-distinguisher {
      type oc-ni-types:route-distinguisher;
      description
        "The route distinguisher that should be used for the local
        VRF or VSI instance when it is signalled via BGP.";
    }

    leaf route-target {
       type oc-ni-types:route-distinguisher;
    }
  }

  grouping protocols-config {
    description
      "Configuration parameters relating to a generic protocol
      instance within a network instance";

    leaf identifier {
      type identityref {
        base "oc-pol-types:INSTALL_PROTOCOL_TYPE";
      }
      description
        "The protocol identifier for the instance";
    }

    leaf name {
      type string;
      description
        "A unique name for the protocol instance";
    }
  }

  uses network-instance-top;
}
