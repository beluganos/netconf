submodule beluganos-bgp-neighbor {

  belongs-to beluganos-bgp {
    prefix "boc-bgp";
  }

  import openconfig-extensions { prefix oc-ext; }
  // import openconfig-inet-types { prefix oc-inet; }
  import beluganos-routing-policy { prefix boc-rpol; }

  // Include the common submodule
  include beluganos-bgp-common;
  include beluganos-bgp-common-multiprotocol;

  // meta
  organization
    "OpenConfig working group";

  contact
    "OpenConfig working group
    netopenconfig@googlegroups.com";

  description
    "This sub-module contains groupings that are specific to the
    neighbor context of the OpenConfig BGP module.";

  oc-ext:openconfig-version "4.0.1";

  revision "2017-10-20" {
    description
      "Clarification of add-paths send-max leaf";
    reference "0.0.1";
  }

  grouping bgp-neighbor-config {
    description
      "Configuration parameters relating to a base BGP neighbor that
      are not also applicable to any other context
      (e.g., peer group)";

    leaf neighbor-address {
      // @BEL changed to string
      //  type oc-inet:ipv4-address;
      type string;
        description
          "Address of the BGP peer, either in IPv4 or IPv6";
    }
  }

  grouping bgp-neighbor-afi-safi-list {
    description
      "List of address-families associated with the BGP neighbor";
    list afi-safi {
      key "afi-safi-name";

      description
        "AFI,SAFI configuration available for the
        neighbour or group";


      leaf afi-safi-name {
	type leafref {
          path "../config/afi-safi-name";
        }
        description
          "Reference to the AFI-SAFI name used as a key
          for the AFI-SAFI list";
      }

      container config {
	description
          "Configuration parameters for the AFI-SAFI";
        uses bgp-common-mp-afi-safi-config;
      }

      container state {
	//config false;
	//description
        //  "State information relating to the AFI-SAFI";
        //uses bgp-common-mp-afi-safi-config;
        //uses bgp-neighbor-afi-safi-state;
      }
    }
  }

  grouping bgp-neighbor-base {
    description
      "Parameters related to a BGP neighbor";

    container config {
      description
        "Configuration parameters relating to the BGP neighbor or
        group";
      uses bgp-neighbor-config;
      uses bgp-common-neighbor-group-config;
    }
    container state {
      // @BEL
      //config false;
      description
        "State information relating to the BGP neighbor";
      //uses bgp-neighbor-config;
      //uses bgp-common-neighbor-group-config;
      //uses bgp-neighbor-state;
    }

    container timers {
      description
        "Timers related to a BGP neighbor";
      container config {
        description
          "Configuration parameters relating to timers used for the
          BGP neighbor";
        uses bgp-common-neighbor-group-timers-config;
      }
      container state {
	// @BEL
        //config false;
        description
          "State information relating to the timers used for the BGP
          neighbor";
        //uses bgp-common-neighbor-group-timers-config;
        //uses bgp-neighbor-timers-state;
      }
    }

    container transport {
      description
        "Transport session parameters for the BGP neighbor";
      container config {
        description
          "Configuration parameters relating to the transport
          session(s) used for the BGP neighbor";
        uses bgp-common-neighbor-group-transport-config;
      }
      container state {
	// @BRL
        //config false;
        description
          "State information relating to the transport session(s)
          used for the BGP neighbor";
        //uses bgp-common-neighbor-group-transport-config;
        //uses bgp-neighbor-transport-state;
      }
    }

    uses boc-rpol:apply-policy-group;

    container afi-safis {
      description
        "Per-address-family configuration parameters associated with
        the neighbor";
      uses bgp-neighbor-afi-safi-list;
    }
  }

  grouping bgp-neighbor-list {
    description
      "The list of BGP neighbors";

    list neighbor {
      key "neighbor-address";
      description
        "List of BGP neighbors configured on the local system,
        uniquely identified by peer IPv[46] address";

      leaf neighbor-address {
        type leafref {
          path "../config/neighbor-address";
        }
        description
          "Reference to the address of the BGP neighbor used as
          a key in the neighbor list";
      }

      uses bgp-neighbor-base;
    }
  }
}
