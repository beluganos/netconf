submodule beluganos-ospfv3-global {

  belongs-to beluganos-ospfv3 {
    prefix "boc-ospfv3";
  }

  import ietf-yang-types { prefix "yang"; }
  import openconfig-extensions { prefix "oc-ext"; }

  // meta
  organization "OpenConfig working group";

  contact
    "OpenConfig working group
    www.openconfig.net";

  description
    "This submodule provides OSPFv3 configuration and operational
    state parameters that are global to a particular OSPF instance";

  oc-ext:openconfig-version "0.1.1";

  revision "2017-10-20" {
    description
      "Minor formatting fixes.";
    reference "0.1.1";
  }
  
  grouping ospfv3-global-config {
    description
      "Global configuration for OSPFv3";

    leaf router-id {
      type yang:dotted-quad;
      description
        "A 32-bit number represented as a dotted quad assigned to
        each router running the OSPFv3 protocol. This number should
        be unique within the autonomous system";
      reference "rfc2828";
    }
  }

  grouping ospfv3-global-structural {
    description
      "Top level structural grouping for OSPFv3 global parameters";

    container global {
      description
        "Configuration and operational state parameters for settings
        that are global to the OSPFv3 instance";

      container config {
        description
          "Global configuration parameters for OSPFv3";
        uses ospfv3-global-config;
      }

      container state {
	// @BEL
        //config false;
        description
          "Operational state parameters for OSPFv3";
        //uses ospfv3-global-config;
      }
    }
  }
}
